module test_module {
  namespace "http://example.com";
  prefix "test";

  import ietf-netconf-acm {
    prefix nacm;
  }

  import ietf-subscribed-notifications {
    prefix sn;
  }

  feature dummy {
    description "It does absolutely nothing.";
  }

  feature dummy2 {
    description "It does absolutely nothing too.";
  }

  leaf leafInt32 {
    type int32;
  }

  leaf stateLeaf {
    config false;
    type int32;
  }

  leaf-list values {
    ordered-by user;
    type int32;
  }

  leaf leafWithDefault {
    type int32;
    default 123;
  }

  leaf denyAllLeaf {
    nacm:default-deny-all;
    type string;
  }

  container popelnice {
    presence true;
    leaf s {
      type string {
        length "0..10";
      }
    }
    container content {
      list trash {
        key "name";
        leaf name { type string; }
        container cont {
          leaf l { type string; }
        }
      }
    }
  }

  rpc noop {
  }

  rpc deny-all-rpc {
    nacm:default-deny-all;
  }

  rpc shutdown {
    output {
      leaf success {
        type boolean;
      }
    }
  }

  notification ping {
    leaf myLeaf {
      type int32;
    }
  }

  notification silent-ping;
}
